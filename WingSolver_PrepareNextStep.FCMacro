import FreeCAD


desc=FreeCAD.ActiveDocument.getObjectsByLabel("ParameterDescription")[0]
current=FreeCAD.ActiveDocument.getObjectsByLabel("CurrentParameter")[0]
sstate=FreeCAD.ActiveDocument.getObjectsByLabel("SolverState")[0]

paramnames=desc.cells[desc.cells["ParameterNames"]]
paramdefaults=desc.cells[desc.cells["DefaultValues"]]
parammins=desc.cells[desc.cells["MinValue"]]
parammaxs=desc.cells[desc.cells["MaxValue"]]
paramsteps=desc.cells[desc.cells["SensibleStepWidth"]]

gradienttests=(0,)+paramnames
currents=sstate.cells["A1"]
costs=sstate.cells["B1"]
gradients=sstate.cells["C1"]

if len(gradienttests)!=len(currents) or len(costs)!=len(currents) or len(gradients)!=len(costs):
		raise Exception("Error: Wrong number of gradients stored in solverstate table. Please fix or start over. You can run CalcGradients Macro")


import numpy as np

npgrad=np.array(gradients)
l=np.linalg.norm(npgrad)
if (l>0):
	npgrad=npgrad/l

steps=tuple(npgrad*desc.cells["LearningRate"]*-1)

params={}
for i in range(len(paramnames)):
	params[paramnames[i]]={"name":paramnames[i],"default":paramdefaults[i],"min":parammins[i],"max":parammaxs[i],"step":steps[i+1]*paramsteps[i], "current":currents[i+1]} #currents and steps has num params + 1 for the old state

	print("Update for %s: %E + %E"%(paramnames[i],params[paramnames[i]]["current"],params[paramnames[i]]["step"]))
	params[paramnames[i]]["current"]+=params[paramnames[i]]["step"]
	
	#check if parameter is below/above min/max
	if params[paramnames[i]]["current"]<params[paramnames[i]]["min"]:
		params[paramnames[i]]["current"]=params[paramnames[i]]["min"]
		print("limiting %s to lower limit"%paramnames[i])
	if params[paramnames[i]]["current"]>params[paramnames[i]]["max"]:
		params[paramnames[i]]["current"]=params[paramnames[i]]["max"]
		print("limiting %s to upper limit"%paramnames[i])
	if params[paramnames[i]]["current"]!=params[paramnames[i]]["current"]: # this catches NaN
		params[paramnames[i]]["current"]=params[paramnames[i]]["default"]
		print("setting invalid %s default value"%paramnames[i])
	print("%s is now %s"%(paramnames[i],"%E"%params[paramnames[i]]["current"]))
	current.set(paramnames[i],"%E"%params[paramnames[i]]["current"])

current.recompute()
for obj in FreeCAD.ActiveDocument.Objects:
	obj.touch()

FreeCAD.ActiveDocument.recompute() # dimensions just changed all over the place - recompute needed


print("done")
