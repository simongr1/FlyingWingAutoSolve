# -*- coding: utf-8 -*-

import FreeCAD


import numpy as np
import scipy as sp
import math
import re
import WingSolver_dependencies.WingSolver_Dependencies as wd
import WingSolver_dependencies.costfunction as fcost


desc=FreeCAD.ActiveDocument.getObjectsByLabel("ResultDescription")[0]
raw=FreeCAD.ActiveDocument.getObjectsByLabel("RawResultData")[0]
res=FreeCAD.ActiveDocument.getObjectsByLabel("ResultData")[0]
geometry=FreeCAD.ActiveDocument.getObjectsByLabel("WingGeometry")[0]
computed=FreeCAD.ActiveDocument.getObjectsByLabel("ComputedValues")[0]

paramnames=desc.cells[desc.cells["ParameterNames"]]
paramfields=desc.cells[desc.cells["Fields"]]
paramapprox=desc.cells[desc.cells["Approx"]]
paramref=desc.cells[desc.cells["Ref"]]
params={}
for i in range(len(paramnames)):
	params[paramnames[i]]={"name":paramnames[i],"rank":paramapprox[i],"ref":paramref[i], "data":np.array(raw.cells[paramfields[i]])}

for param in params.values():
	if param["ref"] in paramnames:
		
		if param["name"]=="PitchTorque":
			#special case for pitch torque. We only want the zero value and two more on each side.
			#The first point is from the raw data is ignored
			middle_index=4 #the 4th(index) point is on y axis
			width_index=2 #additional 2 points on each side
			left_index= middle_index-width_index
			rigth_index= middle_index+width_index+1
			param["refdata"]=params[param["ref"]]["data"]
			fit=np.polyfit(param["refdata"][left_index:rigth_index],param["data"][left_index:rigth_index],param["rank"])
			
		else:
			param["refdata"]=params[param["ref"]]["data"]
			fit=np.polyfit(param["refdata"],param["data"],param["rank"])
		param["center"]=0
		param["slope"]=1.0
		if (param["rank"]==1): # its a line - get slope and zero point crossing
			param["center"]=-fit[1]/fit[0]
			param["slope"]=fit[0]
		elif (param["rank"]==2): # this is for drag - get the point of minimum drag and how quickly it increases
			param["center"]=-fit[1]/(2*fit[0]) #vertex of parabola
			param["slope"]=2*fit[0]
		elif (param["rank"]==3): # this is for lift - a sine wave
			roots=np.roots(fit)
			reals=roots[np.isreal(roots)]
			best=np.inf
			for r in reals:
				if np.abs(r)<np.abs(best):
					best=r
			param["center"]=best
			param["slope"]=3.*fit[0]*best**2 + 2*fit[1]*best + fit[2] # derivative
		param["ZeroValue"]=fit[-1]
		res.set(param["name"]+"Parameters","tuple"+str(tuple([ float(x) for x in fit ])))
		#res.set(param["name"]+"Parameters","=tuple"+str(tuple(fit)))
		res.set(param["name"]+"Center","%E"%param["center"]) #(root of the polynomial
		res.set(param["name"]+"Slope","%E"%param["slope"])
		res.set(param["name"]+"ZeroValue","%E"%fit[-1])
FreeCAD.ActiveDocument.recompute() #recompute to get the calculated fits
#calculate Drag Polar
AIR_DENSITY=1.2
GRAVITY_CONSTANT=9.81
velocity=geometry.get("Velocity")
area_msq=geometry.get("WingArea")*1e-6
mass_kg=computed.get("TotalMass")
lift_force_N=params["LiftForce"]["data"]
drag_force_N=params["DragForce"]["data"]
lift_coefficient=wd.total_to_coefficient(lift_force_N,AIR_DENSITY,velocity,area_msq)
drag_coefficient=wd.total_to_coefficient(drag_force_N,AIR_DENSITY,velocity,area_msq)
drag_curve_poly=wd.drag_curve(lift_coefficient,drag_coefficient)
res.set("DragPolarParameters","tuple"+str(tuple([ float(x) for x in drag_curve_poly ])))


#Cost Function 2
#Calculate Costs 
#Lift and drag


Weigth_N=mass_kg*GRAVITY_CONSTANT
Lift_zero_N= params["LiftForce"]["ZeroValue"]
Drag_zero_N= params["DragForce"]["ZeroValue"]

#pitch stability
#in trimmed position alpha=0
pitch_torque_trimmed_fligth=res.get("PitchTorqueZeroValue") # must be zero
#calculate static margin:
staticMarginGoal=0.12
TaperRatio=geometry.get("TaperRatio")
RootChord=geometry.get("RootChord")
meanChordLength_mm=2/3*RootChord*(1+TaperRatio+TaperRatio**2)/(1+TaperRatio)
alphaZeroLift=params["LiftForce"]["center"]
pitch_torque_AC=np.polyval(wd.extract_tupel(res.get("PitchTorqueParameters")),alphaZeroLift) #evalute pitch torque at zero lift angle

try:
	#catch possible division by zero
	liftForcePoly=wd.extract_tupel(res.get("LiftForceParameters"))
	pitchTorquePoly=wd.extract_tupel(res.get("PitchTorqueParameters"))
	xPositionaAC_reverse_m=(pitch_torque_AC-pitchTorquePoly[-1])/liftForcePoly[-1] #calculate ac position for alpha=0
	
except: 
	print("division by zero, use different point for stability calculation")
	i=int(len(lift_force_N)/2) #take middle value
	xPositionaAC_reverse_m=(pitch_torque_AC-params["PitchTorque"]["data"][i])/lift_force_N[i]

staticMargin= xPositionaAC_reverse_m/(meanChordLength_mm*1e-3)

#Error calculation
#set weights
weights={'SM':1,'trim':1,'lift':1,'power':1}
SM_weight=weights["SM"]
trim_weight=weights["trim"]
lift_weight=weights["lift"]
power_weight=weights["power"]

Lift_cost=fcost.lift_cost(1,1,lift_weight,Lift_zero_N,mass_kg)

static_margin_cost= fcost.static_margin_cost(SM_weight,staticMarginGoal,staticMargin)

pitch_torque_trimmed_cost = fcost.trim_cost(1,1,trim_weight,pitch_torque_trimmed_fligth)
powerBattery= 29.48 # in watt
power_cost= fcost.power_cost(velocity**2,velocity,power_weight,powerBattery,Drag_zero_N)
powerRequired=Drag_zero_N*velocity
#must be zero



cost=Lift_cost+static_margin_cost+pitch_torque_trimmed_cost+power_cost
res.set("LiftGoal","%E"%Weigth_N)
res.set("PowerGoal","%E"%powerBattery)
res.set("StaticMarginGoal","%E"%staticMarginGoal)
res.set("TrimGoal","%E"%0.5)
res.set("LiftCurrent","%E"%Lift_zero_N)
res.set("PowerCurrent","%E"%powerRequired)
res.set("StaticMarginCurrent","%E"%staticMargin)
res.set("TrimCurrent","%E"%pitch_torque_trimmed_fligth)
res.set("LiftCost","%E"%Lift_cost)
res.set("PowerCost","%E"%power_cost)
res.set("StaticMarginCost","%E"%static_margin_cost)
res.set("TrimCost","%E"%pitch_torque_trimmed_cost)

res.set("TotalCost","%E"%cost)


FreeCAD.ActiveDocument.recompute()
