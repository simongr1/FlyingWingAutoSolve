import re
import FreeCADGui
import pandas as pd
# This script gets the expression of the secelcte part and aves them in the csv file at csv_file_path
# Define the CSV file path
csv_file_path = "~/Desktop/info.csv"

# Function to append data to the CSV using pandas
def append_to_csv(data):
    try:
        # Load the existing data (if any)
        try:
            df = pd.read_csv(csv_file_path)
        except FileNotFoundError:
            # If the file doesn't exist, create a new dataframe with the headers
            df = pd.DataFrame(columns=['Object', 'Property', 'BaseKeyword.WordAfterDot', 'Expression'])

        # Append new data
        df = pd.concat([df, pd.DataFrame(data, columns=df.columns)], ignore_index=True)
        # Write to the CSV file
        df.to_csv(csv_file_path, index=False)
        print("Data appended to CSV.")
    except Exception as e:
        print(f"Error writing to CSV: {e}")

def get_Expressions(obj):
    # Access the ExpressionEngine (list of tuples: [(property, expression), ...])
            expression_engine = obj.ExpressionEngine
            if expression_engine:
                # List to hold all extracted data for this selection
                data_to_append = []
                for prop_name, expression in expression_engine:
                    # Extract <<word>>.word patterns
                    matches = re.findall(r'<<(.+?)>>\.(\w+)', expression)
                    for base_keyword, after_dot in matches:
                        # Prepare the data row with switched columns
                        row_data = [
                            obj.Name,     # Object name
                            prop_name,    # Property name
                            f"{base_keyword}.{after_dot}",  # Base keyword and word after dot
                            expression    # Full expression
                        ]
                        # Add the row to the list
                        data_to_append.append(row_data)
                        
                # If there is data to append, do so
                if data_to_append:
                    append_to_csv(data_to_append)

# Get the active document
doc = FreeCAD.ActiveDocument
if doc is None:
    print("No active document found!")
else:
    # Get the selected objects in the GUI
    selection = FreeCADGui.Selection.getSelection()
    if not selection:
        print("No object selected!")
    else:
        # Iterate through selected objects
        for obj in selection:
            get_Expressions(obj)
            if "Sources" in obj.PropertiesList:
                 for obj2 in obj.Sources:
                      get_Expressions(obj2)
            elif "Group" in obj.PropertiesList:
                 print("in the loop")
                 for obj2 in obj.Group:
                      get_Expressions(obj2)
