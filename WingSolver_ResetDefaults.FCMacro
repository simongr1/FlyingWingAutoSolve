# -*- coding: utf-8 -*-

import FreeCAD

from os import path
from CfdOF.Mesh import CfdMeshTools
from CfdOF import CfdTools
from CfdOF.Solve import CfdCaseWriterFoam
import copy
import WingSolver_dependencies.WingSolver_Dependencies as wd 

mydir = path.dirname(__file__)

analyseCSVMacro=path.join(mydir, 'WingSolver_AnalyseResult.FCMacro')

desc=FreeCAD.ActiveDocument.getObjectsByLabel("ParameterDescription")[0]
current=FreeCAD.ActiveDocument.getObjectsByLabel("CurrentParameter")[0]
scontrol=FreeCAD.ActiveDocument.getObjectsByLabel("SolverControl")[0]
geometry=FreeCAD.ActiveDocument.getObjectsByLabel("WingGeometry")[0]
current=FreeCAD.ActiveDocument.getObjectsByLabel("CurrentParameter")[0]

basedir=desc.cells["BaseDir"]
workingdirbase=path.join(basedir,"workingdir")

paramnames=desc.cells[desc.cells["ParameterNames"]]
paramdefaults=desc.cells[desc.cells["DefaultValues"]]
parammins=desc.cells[desc.cells["MinValue"]]
parammaxs=desc.cells[desc.cells["MaxValue"]]
paramsteps=desc.cells[desc.cells["SensibleStepWidth"]]

#reset learning rate
print("Resetting learning rate")
desc.set("LearningRate",str(scontrol.cells["InitialLearningRate"]))

params={}
for i in range(len(paramnames)):
	params[paramnames[i]]={"name":paramnames[i],"default":paramdefaults[i],"min":parammins[i],"max":parammins[i],"step":paramsteps[i], "current":current.cells[paramnames[i]]}

# reset to old values	
current.set("WorkingDir",workingdirbase)
for pn in params:
	print("Setting %s to %s"%(pn,"%E"%params[pn]["default"]))
	current.set(pn,"%E"%params[pn]["default"])

#reset U file
velocity= desc.get("Velocity")
wd.update_velocity(path.join(mydir,"U_template"),velocity,path.join(mydir,"U"))
current.set("Velocity","%f"%velocity)
print(f"U-file reset to {velocity} m/s")

current.recompute()
for obj in FreeCAD.ActiveDocument.Objects:
    obj.touch()
FreeCAD.ActiveDocument.recompute()

print("Reset Defaults: done.")
