# -*- coding: utf-8 -*-

#import FreeCADGui


import numpy as np
import scipy as sp
import matplotlib.pyplot as plt
from matplotlib import cm,colors
import re
import csv
import os
import math

def read_csv(csv_path):
    # Open the CSV file
    with open(csv_path, "r") as file:
        reader = csv.reader(file)  # Read the CSV file
        rows = list(reader)        # Convert the reader object to a list
    return rows
#Extract parameters of out of the csv
def extract_tupel(cell_content):
    #cell_content = "tuple(-0.0876859194475919; -0.390034184491187; -3.2973569606838)"
    # Extract numbers using a regular expression
    numbers = re.findall(r"-?\d+\.\d+", cell_content)  # Matches decimal numbers, including negatives

    # Convert the strings to floats
    numbers = [float(num) for num in numbers]
    return numbers #extracted list


def calculate_function(reference,coefficients):
    # Define the polynomial coefficients as a tuple
    #coefficients = (-0.00601809876176738, -0.0602287380735399, 7.39222409124886, 44.7487686030506)  # Example: x^2 - 3x + 2

    # Generate the polynomial function from the coefficients
    polynomial = np.poly1d(coefficients)

    # Generate x values for plotting
    x = reference  

    # Evaluate the polynomial for the x values
    y = polynomial(x)

    return y


#You also need to add a 1st iteration
#Get subfolders and sort them
working_dir= "/home/sgrimm/src/FlyingWing/results"

dirs = [d for d in os.listdir(working_dir) if os.path.isdir(os.path.join(working_dir, d))]
dirs=sorted(dirs,key=int)

#Results
iterations=len(dirs)
names_alpha=["LiftForce","DragForce","PitchTorque"]
names_beta=["RollTorque","YawTorque"]
names_iterations=["TotalCost"]
alpha=range(-20,20,1)
beta=range(-20,20,1)

LiftForcePoly=[]
DragForcePoly=[]
PitchTorquePoly=[]
RollTorquePoly=[]
YawTorquePoly=[]
TotalCost=[]

data={"LiftForce":LiftForcePoly,"DragForce":DragForcePoly,
                  "PitchTorque":PitchTorquePoly,"RollTorque":RollTorquePoly,"YawTorque":YawTorquePoly, "TotalCost":TotalCost}
results={"names_alpha":names_alpha,"names_beta":names_beta,"alpha":alpha,"beta":beta,"data":data}

for dir in dirs:
    path=os.path.join(working_dir,dir,"0")
    path_res= os.path.join(path,"result.csv")
    rows_res=read_csv(path_res)
    cells =rows_res[1][1:] #The first cell contains the name of the row
    polynomials=[extract_tupel(cell) for cell in cells] #extract the polynomial
    LiftForce,DragForce,PitchTorque,RollTorque,YawTorque=polynomials
    TotalCost_value=float(rows_res[30][-1])
    LiftForcePoly.append(LiftForce)
    DragForcePoly.append(DragForce)
    PitchTorquePoly.append(PitchTorque)
    RollTorquePoly.append(RollTorque)
    YawTorquePoly.append(YawTorque)
    TotalCost.append(TotalCost_value)
    
    


def plotit(parameter_name,names,results,iterations):
    x= results[parameter_name]
    number_of_iterations= iterations
    fraction_of_iterations= 5  # set to 2 to only plot half the iterations
    # Create a figure with subplots
    n_plots=len(names)
    cols=3
    rows= math.ceil(n_plots/cols)
    fig, axes = plt.subplots(rows, cols, figsize=(10, 6))
    cmap = cm.Greys
    norm= colors.Normalize(vmin=1, vmax=number_of_iterations)
    colors_list= cmap(norm(range(1, number_of_iterations +1 )))

    # Plot on each subplot
    for i, ax in enumerate(axes.flat):  # Flatten axes for easier indexing
        if i < n_plots:
            name=names[i]
            # Use a colormap to generate progressively lighter colors
            #colors = cm.viridis(np.linspace(0.2, 1, number_of_iterations))  # Adjust range for lighter colors

            #plot all iterations
            for iteration in range(0,number_of_iterations,fraction_of_iterations):
                poly = results["data"][name][iteration]  # Generate data for plot
                y= calculate_function(x,poly)
                ax.plot(x, y, color=colors_list[iteration])
            ax.set_title(name)
            ax.set_xlabel(parameter_name+" [°]")
            ax.grid(True)
            
        else:
            # Turn off unused axes
            ax.axis('off')

    # Adjust layout
    #fig.suptitle()
    # Add the colorbar
    sm = cm.ScalarMappable(cmap=cmap, norm=norm)  # Scalar mappable for the colorbar
    sm.set_array([])  # Required for ScalarMappable
    cbar = plt.colorbar(sm)
    cbar.set_label("Iteration Number", fontsize=12)  # Label for the colorbar

    plt.legend()
    plt.tight_layout()
    return fig

def plotcosts(costs):
    plt.figure()
    x=range(1,len(costs)+1)
    plt.scatter(x,costs,color="red",label="Data")
    plt.title("Costfunction")
    plt.xlabel("Iterations")
    plt.ylabel("Cost")
    plt.show()
#plot alphas
plotit("alpha",results["names_alpha"],results,iterations)
fig=plotit("beta",results["names_beta"],results,iterations)
costs=results["data"]["TotalCost"]
#costs.append(results["data"][i]["TotalCost"] for i in range(0,len(results["data"])))
plotcosts(costs)
plt.show()


# plot betas
# 
# 
# plot rest   
#print(data)

#Analyse Results:-------------


#calculate course of graph
# different alpha or beta and calculate the resulting function as vector
# do this for every iteration of the base case (0)
"""
sstate=FreeCAD.ActiveDocument.getObjectsByLabel("SolverState")[0]
iterations=int(re.findall('\d+',sstate.getUsedRange()[1])[0])-1
print(iterations)
cells_costs = "B1"+":B"+str(iterations)
iterations_vector = range(1, iterations+1)

#Extract cost from sstate Costs
costvector=sstate.cells[cells_costs]
isolated_costs=[]
for costs in costvector:
    isolated_costs.append(costs[0])
isolated_costs=isolated_costs[::-1]





# Create a grid of subplots
rows, cols = 2,1  # Grid layout: 2 rows, 2 columns
fig, axes = plt.subplots(rows, cols, figsize=(12, 8), sharex=True, sharey=True)

# Titles for each subplot
titles = ['Costs', "Costs again"]
#Vectors
vectors=[isolated_costs, isolated_costs]
# Plot each cost vector in the grid
for i, ax in enumerate(axes.flat):  # Flatten the grid to iterate easily
    ax.plot(iterations_vector, vectors[i], marker='o', linestyle='-', label=f'Series {i+1}')
    ax.set_title(titles[i], fontsize=12)
    ax.set_xlabel('Iteration', fontsize=10)
    ax.set_ylabel('Cost', fontsize=10)
    ax.grid(True, linestyle='--', alpha=0.6)
    ax.legend(fontsize=9)
    ax.set_xticks(iterations_vector)


# Adjust layout to prevent overlapping
plt.tight_layout()

# Show the plots
plt.show()
"""
